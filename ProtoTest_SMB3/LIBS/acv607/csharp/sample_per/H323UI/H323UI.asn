-- This is a cut-down version of the H.323 ASN.1 specifications to 
-- demonstrate the encoding of a sample component in an H.323 UI message.

H323UI DEFINITIONS AUTOMATIC TAGS ::=
BEGIN

H323-UserInformation ::= SEQUENCE		-- root for all Q.931 related ASN.1
{
	h323-uu-pdu	H323-UU-PDU,
	user-data	SEQUENCE
	{
		protocol-discriminator		INTEGER	(0..255),
		user-information		OCTET STRING (SIZE(1..131)),
		...
	} OPTIONAL,
	...
}

-- This is the main PDU type.  NULL's have been used in place of the 
-- actual component types for many of the entries to keep the size of 
-- specification small.

H323-UU-PDU ::= SEQUENCE
{
	h323-message-body   CHOICE
	{
		setup			Setup-UUIE,
		callProceeding		NULL,
		connect			NULL,
		alerting		NULL,
		information		NULL,
		releaseComplete		NULL,
		facility		NULL,
		...,
		progress		NULL,
		empty			NULL		-- used when a FACILITY message is sent,
-- but the Facility-UUIE is not to be invoked
-- (possible when transporting supplementary
-- services messages)
	},
	nonStandardData	NonStandardParameter OPTIONAL,
	...,
	h4501SupplementaryService	SEQUENCE OF OCTET STRING OPTIONAL,
						-- each sequence of octet string is defined as one
						-- H4501SupplementaryService APDU as defined in
						-- Table 3/H.450.1
	h245Tunneling			BOOLEAN,
						-- if TRUE, tunneling of H.245 messages is enabled
	h245Control			SEQUENCE OF OCTET STRING OPTIONAL,
						-- each octet string may contain exactly
						-- one H.245 PDU
	nonStandardControl		SEQUENCE OF NonStandardParameter OPTIONAL
}

Setup-UUIE ::= SEQUENCE
{
	protocolIdentifier	ProtocolIdentifier,
	h245Address		TransportAddress OPTIONAL,
	sourceAddress		SEQUENCE OF AliasAddress OPTIONAL,
	sourceInfo		EndpointType,
	destinationAddress	SEQUENCE OF AliasAddress OPTIONAL,
	destCallSignalAddress	TransportAddress OPTIONAL,
	destExtraCallInfo	SEQUENCE OF AliasAddress OPTIONAL,	-- Note(1) 
	destExtraCRV		SEQUENCE OF CallReferenceValue OPTIONAL,-- Note(1)
	activeMC		BOOLEAN,
	conferenceID		ConferenceIdentifier,
	conferenceGoal		CHOICE
	{
		create		NULL,
		join		NULL,
		invite		NULL,
		...,
		capability-negotiation		NULL,
		callIndependentSupplementaryService	NULL
	},
	callServices		QseriesOptions  OPTIONAL,
	callType		CallType,
	...,
	sourceCallSignalAddress	TransportAddress OPTIONAL,
	remoteExtensionAddress	AliasAddress OPTIONAL,
	callIdentifier		CallIdentifier,
	h245SecurityCapability	SEQUENCE OF H245Security OPTIONAL,
	tokens			SEQUENCE OF ClearToken OPTIONAL,
	cryptoTokens		SEQUENCE OF CryptoH323Token OPTIONAL,
	fastStart		SEQUENCE OF OCTET STRING OPTIONAL,
	mediaWaitForConnect	BOOLEAN,
	canOverlapSend		BOOLEAN,
	endpointIdentifier	EndpointIdentifier OPTIONAL

}

ClearToken ::= INTEGER          -- dummy def (not used in sample)
CryptoH323Token ::= INTEGER     -- dummy def (not used in sample)

CallType ::= CHOICE
{
	pointToPoint	NULL,		-- Point to point
	oneToN		NULL,		-- no interaction (FFS)
	nToOne		NULL,		-- no interaction (FFS)
	nToN		NULL,		-- interactive (multipoint)
	...
}

QseriesOptions ::= SEQUENCE
{
	q932Full	BOOLEAN,	-- if true, indicates full support for Q.932
	q951Full	BOOLEAN, 	-- if true, indicates full support for Q.951
	q952Full	BOOLEAN, 	-- if true, indicates full support for Q.952
	q953Full	BOOLEAN, 	-- if true, indicates full support for Q.953
	q955Full	BOOLEAN, 	-- if true, indicates full support for Q.955
	q956Full	BOOLEAN, 	-- if true, indicates full support for Q.956
	q957Full	BOOLEAN, 	-- if true, indicates full support for Q.957
	q954Info	Q954Details,	
	...
}

Q954Details ::= SEQUENCE
{
	conferenceCalling	BOOLEAN,
	threePartyService	BOOLEAN,
	...
}

BandWidth		::=	INTEGER (0.. 4294967295)	-- in 100s of bits
GloballyUniqueID	::=	OCTET STRING (SIZE(16))
ConferenceIdentifier	::=	GloballyUniqueID
CallReferenceValue	::=	INTEGER (0..65535)
GatekeeperIdentifier	::=	BMPString (SIZE(1..128))
EndpointIdentifier	::=	BMPString (SIZE(1..128))
RequestSeqNum		::=	INTEGER (1..65535)
ProtocolIdentifier	::=	OBJECT IDENTIFIER	
				-- shall be set to  
				-- {itu-t (0) recommendation (0) h (8) 2250 version (0) 2}
TimeToLive		::=	INTEGER (1..4294967295)		--in seconds

CallIdentifier ::= SEQUENCE
{
	guid		GloballyUniqueID,
	...
}

EndpointType ::= SEQUENCE
{
	nonStandardData	NonStandardParameter OPTIONAL,
	vendor			VendorIdentifier OPTIONAL,
	gatekeeper		GatekeeperInfo OPTIONAL,
	gateway			GatewayInfo OPTIONAL,
	mcu			McuInfo OPTIONAL,	-- mc must be set as well
	terminal		TerminalInfo OPTIONAL,
	mc			BOOLEAN,		-- shall not be set by itself
	undefinedNode		BOOLEAN,	
	...,
	set	BIT STRING (SIZE(32)) OPTIONAL
			-- shall not be used with mc, gatekeeper
			-- code points for the various SET devices
			-- are defined in the respective SET
			-- Annexes
}

GatewayInfo ::= SEQUENCE
{
	protocol		SEQUENCE OF SupportedProtocols OPTIONAL,
	nonStandardData	NonStandardParameter OPTIONAL,
	...
}

SupportedProtocols ::= CHOICE
{
	nonStandardData	NonStandardParameter,
	h310			H310Caps,
	h320			H320Caps,
	h321			H321Caps,
	h322			H322Caps,
	h323			H323Caps,
	h324			H324Caps,
	voice			VoiceCaps,
	t120-only		T120OnlyCaps,
	...,
	nonStandardProtocol	NonStandardProtocol
}

H310Caps ::= SEQUENCE
{
	nonStandardData	NonStandardParameter OPTIONAL,
	...,
	dataRatesSupported	SEQUENCE OF DataRate OPTIONAL,
	supportedPrefixes	SEQUENCE OF SupportedPrefix
}

H320Caps ::= SEQUENCE
{
	nonStandardData	NonStandardParameter OPTIONAL,
	...,
	dataRatesSupported	SEQUENCE OF DataRate OPTIONAL,
	supportedPrefixes	SEQUENCE OF SupportedPrefix
}

H321Caps ::= SEQUENCE
{
	nonStandardData	NonStandardParameter OPTIONAL,
	...,
	dataRatesSupported	SEQUENCE OF DataRate OPTIONAL,
	supportedPrefixes	SEQUENCE OF SupportedPrefix
}

H322Caps ::= SEQUENCE
{
	nonStandardData	NonStandardParameter OPTIONAL,
	...,
	dataRatesSupported	SEQUENCE OF DataRate OPTIONAL,
	supportedPrefixes	SEQUENCE OF SupportedPrefix
}

H323Caps ::= SEQUENCE
{
	nonStandardData	NonStandardParameter OPTIONAL,
	...,
	dataRatesSupported	SEQUENCE OF DataRate OPTIONAL,
	supportedPrefixes	SEQUENCE OF SupportedPrefix
}

H324Caps ::= SEQUENCE
{
	nonStandardData	NonStandardParameter OPTIONAL,
	...,
	dataRatesSupported	SEQUENCE OF DataRate OPTIONAL,
	supportedPrefixes	SEQUENCE OF SupportedPrefix
}

VoiceCaps ::= SEQUENCE
{
	nonStandardData	NonStandardParameter OPTIONAL,
	...,
	dataRatesSupported	SEQUENCE OF DataRate OPTIONAL,
	supportedPrefixes	SEQUENCE OF SupportedPrefix
}

T120OnlyCaps ::= SEQUENCE
{
	nonStandardData	NonStandardParameter OPTIONAL,
	...,
	dataRatesSupported	SEQUENCE OF DataRate OPTIONAL,
	supportedPrefixes	SEQUENCE OF SupportedPrefix
}

NonStandardProtocol ::= SEQUENCE
{
	nonStandardData	NonStandardParameter OPTIONAL,
	dataRatesSupported	SEQUENCE OF DataRate OPTIONAL,
	supportedPrefixes	SEQUENCE OF SupportedPrefix,
	...
}

McuInfo ::=SEQUENCE
{
	nonStandardData	NonStandardParameter OPTIONAL,
	...
}

TerminalInfo ::=SEQUENCE 
{
	nonStandardData	NonStandardParameter OPTIONAL,
	...
}

GatekeeperInfo ::=SEQUENCE 
{
	nonStandardData	NonStandardParameter OPTIONAL,
	...
}

VendorIdentifier ::= SEQUENCE
{
	vendor			H221NonStandard,
	productId		OCTET STRING (SIZE(1..256)) OPTIONAL,	-- per vendor
	versionId		OCTET STRING (SIZE(1..256)) OPTIONAL,	-- per product
	...
}

H221NonStandard ::= SEQUENCE
{	t35CountryCode		INTEGER(0..255),	-- country, as per T.35
	t35Extension		INTEGER(0..255),	-- assigned nationally
	manufacturerCode	INTEGER(0..65535),	-- assigned nationally
	...
}

NonStandardParameter ::= SEQUENCE
{
	nonStandardIdentifier	NonStandardIdentifier,
	data			OCTET STRING
}

NonStandardIdentifier		::=CHOICE
{
	object			OBJECT IDENTIFIER,
	h221NonStandard	H221NonStandard,
	...
}

TransportAddress ::= CHOICE
{
	ipAddress	SEQUENCE
	{
		ip		OCTET STRING (SIZE(4)),
		port		INTEGER(0..65535)
	},
	ipSourceRoute	SEQUENCE
	{
		ip		OCTET STRING (SIZE(4)),
		port		INTEGER(0..65535),
		route		SEQUENCE OF OCTET STRING(SIZE(4)),
		routing 	CHOICE
		{
			strict	NULL,
			loose	NULL,
			...
		},
		...
	},
	ipxAddress	SEQUENCE
	{
		node	OCTET STRING (SIZE(6)),
		netnum	OCTET STRING (SIZE(4)),
		port	OCTET STRING (SIZE(2))
	},
	ip6Address	SEQUENCE
	{
		ip	OCTET STRING (SIZE(16)),
		port	INTEGER(0..65535),
		...
	},
	netBios			OCTET STRING (SIZE(16)),
	nsap			OCTET STRING (SIZE(1..20)),
	nonStandardAddress	NonStandardParameter,	
	...	
}

AliasAddress ::= CHOICE
{
	e164		IA5String (SIZE (1..128)) (FROM ("0123456789#*,")),
	h323-ID		BMPString (SIZE (1..256)),	-- Basic ISO/IEC 10646-1 (Unicode)
	...,
	url-ID		IA5String (SIZE(1..512)),	-- URL style address
	transportID	TransportAddress,
	email-ID	IA5String (SIZE(1..512)),	-- rfc822-compliant email address
	partyNumber	NULL  -- PartyNumber
}	

SecurityServiceMode ::= CHOICE 
{
nonStandard		NonStandardParameter,
none			NULL,
default			NULL,
...				-- can be extended with other specific modes
}

SecurityCapabilities ::= SEQUENCE 
{
	nonStandard		NonStandardParameter OPTIONAL,
	encryption		SecurityServiceMode,
	authenticaton		SecurityServiceMode,
	integrity		SecurityServiceMode,
...
}

H245Security ::= CHOICE 
{
	nonStandard		NonStandardParameter,
	noSecurity		NULL,
	tls			SecurityCapabilities,
	ipsec			SecurityCapabilities,
	...
}

DataRate ::= SEQUENCE
{
	nonStandardData	NonStandardParameter OPTIONAL,
	channelRate		BandWidth,
	channelMultiplier	INTEGER (1..256) OPTIONAL,
	...
}

SupportedPrefix ::= SEQUENCE
{
	nonStandardData	NonStandardParameter OPTIONAL,
	prefix			AliasAddress,
	...
}

END
